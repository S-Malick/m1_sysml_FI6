package spi{
    package requirements{
        requirement consulterPlaceLibre specializes fonctions{
            doc
        }

        requirement seGarerSoiMeme specializes fonctions{
            doc
        }

        requirement deposerVehiculeBox specializes fonctions{
            doc
        }

        requirement demanderRecharge specializes fonctions{
            doc
        }

        requirement suivreVehicule specializes fonctions{
            doc
        }

        requirement retournerAPiedAuVehicule specializes fonctions{
            doc
        }

        requirement recupererVehicule specializes fonctions{
            doc
        }

        requirement demanderAssistance specializes fonctions{
            doc
        }

        requirement superviserParking specializes fonctions{
            doc
        }

        requirement consulterHistorique specializes fonctions{
            doc
        }

        requirement gererIncident specializes fonctions{
            doc
        }

        requirement entretenirSysteme specializes fonctions{
            doc
        }

        requirement maintenirLeMateriel specializes fonctions{
            doc
        }

        requirement evaluerPerformanceSysteme specializes fonctions{
            doc
        }

        requirement mettreAJourLeLogiciel specializes fonctions{
            doc
        }

        requirement intervenirSurEnginTransport specializes fonctions{
            doc
        }

        requirement detecterOccupation specializes 
    }
}
